-- MIB that references enterprises without importing it
-- Should fail in strict mode, work in permissive mode

MISSING-IMPORT-TEST-MIB DEFINITIONS ::= BEGIN

IMPORTS
    MODULE-IDENTITY, OBJECT-TYPE, Integer32
        FROM SNMPv2-SMI
    DisplayString
        FROM SNMPv2-TC;

-- Note: enterprises is NOT imported from SNMPv2-SMI

missingImportTestMIB MODULE-IDENTITY
    LAST-UPDATED "202601280000Z"
    ORGANIZATION "Test"
    CONTACT-INFO "test@test.com"
    DESCRIPTION "Test MIB for missing import fallback behavior"
    ::= { enterprises 99999 }

-- This object uses enterprises without importing it
testObject OBJECT-TYPE
    SYNTAX      Integer32
    MAX-ACCESS  read-only
    STATUS      current
    DESCRIPTION "A test object"
    ::= { missingImportTestMIB 1 }

END
